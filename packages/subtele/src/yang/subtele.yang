module subtele {
  namespace "http://com/example/subtele";
  prefix subtele;

  import ietf-inet-types {
    prefix inet;
  }
  import tailf-common {
    prefix tailf;
  }
  import tailf-ncs {
    prefix ncs;
  }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description
    "This module contains a collection of YANG definitions
     for Cisco IOS-XR telemetry-model-driven package configuration.

     Copyright (c) 2013-2016 by Cisco Systems, Inc.
     All rights reserved.";

  revision "2015-11-09" {
    description
      "IOS XR 6.0 revision.";
  }

  typedef Proto-type {
    type enumeration {
      enum grpc {
        value 1;
        description "GRPC";
      }
      enum tcp {
        value 2;
        description "tcp";
      }
    }
    description "Proto type";
  }
  typedef Encode-type {
    type enumeration {
      enum gpb {
        value 2;
        description "GPB";
      }
      enum self-describing-gpb {
        value 3;
        description "SELF DESCRIBING GPB";
      }
      enum json {
        value 4;
        description "JSON";
      }
    }
    description "Encode type";
  }
  typedef Cisco-ios-xr-string {
    type string {
      pattern "[\w\-\.:,_@#%$\+=\|;]+";
    }
    description "Special characters are not allowed.";
  }

  augment /ncs:services {

    list subtele {
      description "This is an RFS skeleton service";

      key subscription-id;
      leaf subscription-id {
        tailf:info "Unique service id";
        tailf:cli-allow-range;
        type string;
      }

      uses ncs:service-data;
      ncs:servicepoint subtele-servicepoint;

      tailf:action self-test {
        tailf:info "Perform self-test of the service";
        tailf:actionpoint telemetry-self-test;
        output {
          leaf success {
            type boolean;
          }
          leaf message {
            type string;
            description
              "Free format message.";
          }
        }
      }

      // replace with your own stuff her

      leaf enable {
        type empty;
        description "Enable Model Driven Telemetry Subscription";
      }

      container source-group{
        leaf source-id{
          type Cisco-ios-xr-string;
          description "source group id string";
        }
        leaf-list device{
          type leafref{
            path "/ncs:devices/ncs:device/ncs:name";
          }
        }
      }

      container sensor-group {
        leaf sensor-id {
          type Cisco-ios-xr-string;
          description "The identifier for this group";
        }
        leaf sample-interval {
          type uint32 {
            range "500..3600000";
          }
          units "millisecond";
          description "Sample interval in milliseconds";
        }
        leaf heartbeat-interval {
          type uint32 {
            range "0..4294967295";
          }
          units "second";
          description "Heartbeat interval in Seconds";
        }
        leaf supress-redundant {
          type empty;
          description "Supress Redundant updates";
        }
        leaf-list sensor-path {
          type Cisco-ios-xr-string;
          description "Sensor Path";
        }
      }

      container destination-group{
        leaf destination-id {
          type Cisco-ios-xr-string;
          description "destination group id string";
        }
        leaf encoding {
          type Encode-type;
          description
            "Encoding used to transmit telemetry data to
            the collector";
        }
        leaf protocol {
          type Proto-type;
          description
            "Transport Protocol used to transmit
            telemetry data to the collector";
        }
        leaf destination{
          type Cisco-ios-xr-string;
          description "Destination address and port";
        }
      }

      leaf source-qos-marking {
        type uint32 {
          range "10..300";
        }
        description "Outgoing DSCP value";
      }

      leaf tele_visual{
        type empty;
        description "Enable telemetry visualization";
      }
    }
  }
}
