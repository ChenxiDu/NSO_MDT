module mdt {

  /*** NAMESPACE / PREFIX DEFINITION ***/

  namespace "http://cisco.com/ns/yang/Cisco-IOS-XR-telemetry-model-driven-cfg";

  prefix "telemetry-model-driven-cfg";

  /*** LINKAGE (IMPORTS / INCLUDES) ***/

  import ietf-inet-types { prefix "inet"; }

  /*** META INFORMATION ***/

  organization "Cisco Systems, Inc.";

  contact
    "Cisco Systems, Inc.
     Customer Service

     Postal: 170 West Tasman Drive
     San Jose, CA 95134

     Tel: +1 800 553-NETS

     E-mail: cs-yang@cisco.com";

  description
    "This module contains a collection of YANG definitions
     for Cisco IOS-XR telemetry-model-driven package configuration.

     This module contains definitions
     for the following management objects:
       telemetry-model-driven: Model Driven Telemetry configuration

     Copyright (c) 2013-2016 by Cisco Systems, Inc.
     All rights reserved.";

  revision "2015-11-09" {
    description
      "IOS XR 6.0 revision.";
  }

  typedef Cisco-ios-xr-string {
    type string {
      pattern "[\w\-\.:,_@#%$\+=\|;]+";
    }
    description "Special characters are not allowed.";
  }

  typedef Cisco-ios-xr-port-number {
    type uint16 {
      range "1..65535";
    }
    description "Port number of range from 1 to 65535";
  }

  typedef Proto-type {
    type enumeration {
      enum grpc {
        value 1;
        description "GRPC";
      }
      enum tcp {
        value 2;
        description "tcp";
      }
    }
    description "Proto type";
  }
  typedef Encode-type {
    type enumeration {
      enum gpb {
        value 2;
        description "GPB";
      }
      enum self-describing-gpb {
        value 3;
        description "SELF DESCRIBING GPB";
      }
      enum json {
        value 4;
        description "JSON";
      }
    }
    description "Encode type";
  }
  typedef Af {
    type enumeration {
      enum ipv4 {
        value 1;
        description "IPv4 address family";
      }
      enum ipv6 {
        value 2;
        description "IPv6 address family";
      }
    }
    description "Af";
  }

  container telemetry-model-driven {
    description "Model Driven Telemetry configuration";

    container sensor-groups {
      description "Sensor group configuration";

      list sensor-group {
        key "sensor-group-identifier";
        description "Sensor group configuration";

        container sensor-paths {
          description "Sensor path configuration";

          list sensor-path {
            key "telemetry-sensor-path";
            description "Sensor path configuration";
            leaf telemetry-sensor-path {
              type Cisco-ios-xr-string;
              description "Sensor Path";
            }
          }
        }
        leaf enable {
          type empty;
          description "Enable Sensor Group";
        }
        leaf sensor-group-identifier {
          type Cisco-ios-xr-string;
          description "The identifier for this group";
        }
      }
    }

    container subscriptions {
      description "Streaming Telemetry Subscription";

      list subscription {
        key "subscription-identifier";
        description "Streaming Telemetry Subscription";

        container source-address {
          presence "Indicates a source-address node is configured.";
          description
            "Source address to use for streaming telemetry
            information";
          leaf address-family {
            type Af;
            mandatory true;
            description "Address Family type, IPv4|IPv6";
          }
          leaf ip-address {
            type inet:ipv4-address-no-zone;
            description "Source IPv4 address";
          }
          leaf ipv6-address {
            type string;
            description "IPV6 address of the Source";
          }
        }

        container sensor-profiles {
          description "Associate Sensor Groups with Subscription";

          list sensor-profile {
            key "sensorgroupid";
            description "Associate Sensor Group with Subscription";
            leaf sample-interval {
              type uint32 {
                range "500..3600000";
              }
              units "millisecond";
              description "Sample interval in milliseconds";
            }
            leaf heartbeat-interval {
              type uint32 {
                range "0..4294967295";
              }
              units "second";
              description "Heartbeat interval in Seconds";
            }
            leaf supress-redundant {
              type empty;
              description "Supress Redundant updates";
            }
            leaf sensorgroupid {
              type Cisco-ios-xr-string;
              description
                "Reference to the telemetry sensor group name";
            }
          }
        }

        container destination-profiles {
          description
            "Associate Destination Groups with Subscription";

          list destination-profile {
            key "destination-id";
            description
              "Associate Destination Group with Subscription";
            leaf enable {
              type empty;
              description
                "Associate destintion id with Subscription";
            }
            leaf destination-id {
              type Cisco-ios-xr-string;
              description
                "Destination Id to associate with
                Subscription";
            }
          }
        }
        leaf source-qos-marking {
          type uint32 {
            range "10..300";
          }
          description "Outgoing DSCP value";
        }
        leaf subscription-identifier {
          type Cisco-ios-xr-string;
          description "Subscription identifier string";
        }
      }
    }

    container destination-groups {
      description "Destination Group configuration";

      list destination-group {
        key "destination-id";
        description "Destination Group";

        container destinations {
          description "Destination configuration";

          list destination {
            key "address-family";
            description "Destination address configuration";

            grouping DESTINATION-CONTENT {
              description "DESTINATION CONTENT";
              leaf encoding {
                type Encode-type;
                description
                  "Encoding used to transmit telemetry data to
                  the collector";
              }
              leaf protocol {
                type Proto-type;
                description
                  "Transport Protocol used to transmit
                  telemetry data to the collector";
              }
            }
            leaf address-family {
              type Af;
              description "Address Family type, IPv4|IPv6";
            }

            list ipv4 {
              when "../address-family = 'ipv4'" {
                description "../address-family = IPv4";
              }
              key "ipv4-address destination-port";
              description "ipv4";
              leaf ipv4-address {
                type inet:ip-address-no-zone;
                description "Destination IPv4 address";
              }
              leaf destination-port {
                type Cisco-ios-xr-port-number;
                description "destination port";
              }
              uses DESTINATION-CONTENT;
            }

            list ipv6 {
              when "../address-family = 'ipv6'" {
                description "../address-family = IPv6";
              }
              key "ipv6-address destination-port";
              description "ipv6";
              leaf ipv6-address {
                type Cisco-ios-xr-string;
                description "IPV6 address of the destination";
              }
              leaf destination-port {
                type Cisco-ios-xr-port-number;
                description "destination port";
              }
              uses DESTINATION-CONTENT;
            }
          }
        }
        leaf destination-id {
          type Cisco-ios-xr-string;
          description "destination group id string";
        }
      }
    }
    leaf enable {
      type empty;
      description "Enable Model Driven Telemetry";
    }
  }
}
